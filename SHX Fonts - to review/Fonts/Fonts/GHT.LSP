(defun c:ght    () (ghtxt))
(princ "\n\tc:CHText loaded.  Start command with GHT.")
(princ)
(defun insrt (s l n) (strcat (substr s 1 (1- n)) l (substr s (1+ n))))
(defun cgs (s os ns / sl osl nsl st si)
     (setq osl (strlen os) nsl (strlen ns) si 1)
     (while (= osl (setq sl (strlen (setq st (substr s si osl)))))
	(if (= os st)
	    (setq s (strcat (substr s 1 (1- si)) ns (substr s (+ si osl)))
		  si (+ si nsl))
	    (setq si (1+ si)))) (eval s))
(defun chltr (s ltr1 ltr2 ltr3 ltr4 L L- -L- -L / cnt sltr prvl nxtl tn)
(setq cnt 1)
 (while (= 1 (strlen (setq sltr (substr s cnt 1))))
  (if (or (= ltr1 sltr) (= ltr2 sltr) (= ltr3 sltr) (= ltr4 sltr)) 
   (progn         
	 (if (= 1 cnt) (setq prvl "") (setq prvl (substr s (1- cnt) 1)))
	 (setq nxtl (substr s (1+ cnt) 1))
     (if (or (= prvl "" ) (= prvl " ") (= prvl "H") (= prvl "h") (= prvl "X")
	     (= prvl "x") (= prvl "N") (= prvl "n") (= prvl "]") (= prvl "`")
	     (= prvl "V") (= prvl "v") (= prvl ">") (= prvl ",") (= prvl "C")
	     (= prvl "c") (= prvl "B") (= prvl "b") (= prvl "’") (= prvl "‘")
	     (= prvl "¥") (= prvl "¤") (= prvl "<") (= prvl ")") (= prvl "(")
	     (= prvl "!") (= prvl "?") (= prvl "%") (= nxlt "ð"))
		 (if (or (= nxtl "" ) (= nxtl " ") (= nxlt "<")
			 (= nxtl ")") (= nxtl "(") (= nxlt "!")
			 (= nxlt "?") (= nxlt "%") (= nxlt "ð"))
		     (setq s (insrt s  L  cnt)) (setq s (insrt s  L- cnt)))
		 (if (or (= nxtl "" ) (= nxtl " ") (= nxlt "<")
			 (= nxtl ")") (= nxtl "(") (= nxlt "!")
			 (= nxlt "?") (= nxlt "%") (= nxlt "ð"))
		     (setq s (insrt s -L  cnt)) (setq s (insrt s -L- cnt))))))
  (setq cnt (1+ cnt))) (eval s))
(defun c:ct (/ s e os)
  (setq e (entget (car (entsel "\nSelect text: "))))
  (setq s (cdr (setq os (assoc 1 e))))
  (setq s (chltr s "H" "H" "h" "h" "H" "H" "h" "h"))
  (setq s (chltr s "X" "X" "x" "x" "X" "X" "x" "x"))
  (setq s (chltr s "N" "N" "n" "n" "N" "N" "n" "n"))
  (setq s (chltr s "F" "f" "f" "F" "F" "f" "f" "F"))
  (setq s (chltr s "J" "j" "j" "J" "J" "j" "j" "J"))
  (setq s (chltr s "E" "e" "e" "E" "E" "e" "e" "E"))
  (setq s (chltr s "[" "{" "{" "°" "[" "{" "{" "°"))
  (setq s (chltr s "P" "p" "p" "±" "P" "p" "p" "±"))
  (setq s (chltr s "O" "o" "o" "²" "O" "o" "o" "²"))
  (setq s (chltr s "S" "s" "s" "S" "S" "s" "s" "S"))
  (setq s (chltr s "A" "a" "a" "A" "A" "a" "a" "A"))
  (setq s (chltr s "W" "w" "w" "W" "W" "w" "w" "W"))
  (setq s (chltr s "Q" "q" "q" "Q" "Q" "q" "q" "Q"))
  (setq s (chltr s "U" "u" "–" "š" "U" "u" "–" "š"))
  (setq s (chltr s "Y" "y" "˜" "�" "Y" "y" "˜" "�"))
  (setq s (chltr s "T" "t" "œ" "Ÿ" "T" "t" "œ" "Ÿ"))
  (setq s (chltr s "R" "r" "ž" "R" "R" "r" "ž" "R"))
  (setq s (chltr s ";" ":" "Ê" ";" ";" ":" "Ê" ";"))
  (setq s (chltr s "§" "§" "§" "§" "§" "§" "§" ";"))
  (setq s (chltr s "G" "g" "g" "G" "G" "g" "g" "G"))
  (setq s (chltr s "L" "l" "l" "â" "L" "l" "l" "â"))
  (setq s (chltr s "K" "k" "k" "K" "K" "k" "k" "K"))
  (setq s (chltr s "I" "i" "Œ" "�" "I" "i" "Œ" "�"))
  (setq s (chltr s "D" "d" "d" "å" "D" "d" "d" "å"))
  (setq s (chltr s "Z" "z" "z" "ë" "Z" "z" "z" "ë"))
  (setq s (cgs s "gh" "b")) (setq s (cgs s "gx" "’"))
  (setq s (cgs s "gn" "¥")) (setq s (cgs s "g¦" "½"))
  (setq s (chltr s "B" "B" "b" "b" "B" "B" "b" "b"))
  (setq s (chltr s "’" "’" "‘" "‘" "’" "’" "‘" "‘"))
  (setq s (chltr s "¥" "¥" "¤" "¤" "¥" "¥" "¤" "¤"))
  (setq s (chltr s "M" "M" "m" "m" "M" "j" "j" "m"))
  (setq e (subst (cons 1 s) os e))
  (entmod e)
(princ)
)
(defun c:ang () 
(setq L1 (nentsel "\nSelect first  line:"))
(setq L2 (nentsel "\nSelect second line:"))
(setq int0 (inters 
	   (cdr (assoc 10 (entget (car L1)))) 
	   (osnap (cadr L1) "nea") 
	   (cdr (assoc 10 (entget (car L2)))) 
	   (osnap (cadr L2) "nea") nil))
(if (null int0) (prompt "\n\tThe same line or lines are parallel."))
(if (and  int0) (progn
		       (setq fang (angle int0 (osnap (cadr L1) "nea") ))
		       (setq sang (angle int0 (osnap (cadr L2) "nea") )) 
		       (setq angl (abs (- fang sang)))
		       (if (> angl pi) (setq angl (- (* 2 pi) angl)))
		       (prompt (strcat "\nThe angle is " (angtos angl)))
		)
		       )
(princ)
)
